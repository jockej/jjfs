JjfsCache DEFINITIONS ::= BEGIN

-- A file
JjfsFile ::= SEQUENCE {
    -- name of the file
    name UTF8String,
    -- size in bytes
    size INTEGER
}

-- A directory
JjfsDir ::= SEQUENCE {
    -- name of this directory
    name UTF8String,
    size INTEGER,
    -- files in this directory
    files SEQUENCE OF JjfsFile,
    -- subdirectories of this directory
    subdirs SEQUENCE OF JjfsDir
}

END
